module ietf-yp-provenance {
    yang-version 1.1;
    namespace
    "urn:ietf:params:xml:ns:yang:ietf-yp-provenance";
    prefix inotifprov;

    import ietf-system-capabilities {
        prefix sysc;
        reference
            "RFC 9196: YANG Modules Describing Capabilities for
            Systems and Datastore Update Notifications";
    }
    import ietf-notification-capabilities {
        prefix notc;
        reference
            "RFC 9196: YANG Modules Describing Capabilities for
            Systems and Datastore Update Notifications";
    }
    import ietf-yang-provenance {
        prefix iyangprov;
        reference
            "RFC XXXX: Applying COSE Signatures for YANG Data Provenance";
    }
    import ietf-yang-structure-ext {
        prefix sx;
        reference
            "RFC 8791: YANG Data Structure Extensions";
    }
    import ietf-yp-notification {
        prefix inotenv;
        reference
            "RFC YYYY: Extensible YANG Model for YANG-Push Notifications";
    }

    organization "IETF OPSAWG (Operations and Management Area Working Group)";
    contact
        "WG Web:   <https://datatracker.ietf.org/wg/opsawg/>
        WG List:  <mailto:opsawg@ietf.org>

        Authors:  Alex Huang Feng
        <mailto:alex.huang-feng@insa-lyon.fr>
        Diego Lopez
        <mailto:diego.r.lopez@telefonica.com>
        Antonio Pastor
        <mailto:antonio.pastorperales@telefonica.com>";

    description
        "Defines a bynary provenance-signature type to be used in other YANG
        modules.

        Copyright (c) 2025 IETF Trust and the persons identified as
        authors of the code.  All rights reserved.

        Redistribution and use in source and binary forms, with or without
        modification, is permitted pursuant to, and subject to the license
        terms contained in, the Revised BSD License set forth in Section
        4.c of the IETF Trust's Legal Provisions Relating to IETF Documents
        (https://trustee.ietf.org/license-info).

        This version of this YANG module is part of RFC XXXX; see the RFC
        itself for full legal notices.";

    revision 2025-05-09 {
        description
            "First revision";
        reference
            "RFC XXXX: Applying COSE Signatures for YANG Data Provenance";
    }

    sx:augment-structure "/inotenv:envelope" {
        leaf provenance {
            type iyangprov:provenance-signature;
            description
                "COSE signature of the content of the Notification for
                provenance verification.";
        }
    }

    augment "/sysc:system-capabilities"
    + "/notc:subscription-capabilities"
    + "/inotenv:notification-metadata/inotenv:metadata" {
        description
            "Extensions to Notification Capabilities enabling clients to
            know whether the provenance signature is supported.";
        leaf notification-provenance {
            type boolean;
            default "false";
            description
                "Support of the provenance signature on YANG-Push
                Notifications.";
        }
    }
}
